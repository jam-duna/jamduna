FuzzProtocol DEFINITIONS ::= BEGIN

-- `Block` and `Header` as defined by the gray paper
-- Refer to jam-types.asn in the jam-test-vectors repo

U8 ::= INTEGER (0..255)
U32 ::= INTEGER (0..4294967295)

Hash ::= OCTET STRING (SIZE(32))
HeaderHash ::= Hash
StateRootHash ::= Hash

Version ::= SEQUENCE {
    major U8,
    minor U8,
    patch U8
}

PeerInfo ::= SEQUENCE {
    -- Application version
    app-version  Version,
    -- JAM protocol version
    jam-version  Version,
    -- Application name
    name UTF8String
}

TrieKey ::= OCTET STRING (SIZE(31))

KeyValue ::= SEQUENCE {
    key     TrieKey,
    value   OCTET STRING
}

State ::= SEQUENCE OF KeyValue

ImportBlock ::= Block

SetState ::= SEQUENCE {
    header Header,
    state State
}

GetState ::= HeaderHash

StateRoot ::= StateRootHash

Message ::= CHOICE {
    peer-info    [0] PeerInfo,
    import-block [1] ImportBlock,
    set-state    [2] SetState,
    get-state    [3] GetState,
    state        [4] State,
    state-root   [5] StateRoot
}

END
